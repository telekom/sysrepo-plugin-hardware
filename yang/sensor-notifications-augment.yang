module sensor-notifications-augment {
  yang-version 1.1;
  namespace "http://terastrm.net/ns/yang/sensor-notifications-augment";
  prefix sensor-notif;

  import ietf-hardware {
    prefix hw;
  }

  import iana-hardware {
    prefix ianahw;
  }

  organization
    "Deutsche Telekom AG.";

  revision 2021-05-14 {
    description
      "Initial revision.";
  }

  augment "/hw:hardware/hw:component" {
    if-feature hw:hardware-sensor;
    container sensor-notifications {
      when 'derived-from-or-self(../hw:class,
                             "ianahw:sensor")' {
        description
          "Sensor data nodes present for any component of type
           'sensor'";
      }
      description "Configure threshold notifications for sensors values that are being
        monitored.";
      leaf poll-interval {
        type uint32 {
          range 1..max;
        }
        description "Interval between consecutive sensor data collection triggers";
        default 60;
        units "seconds";
      }
      list threshold {
        description "Configure threshold notifications for sensors values that are being
          monitored.";
        key name;
        leaf name {
          type string;
        }
        choice value {
          mandatory true;
          case max {
            leaf max {
              type hw:sensor-value;
              description "Send notification when the sensor-value exceeds the
                configured threshold";
            }
          }
          case min {
            leaf min {
              type hw:sensor-value;
              description "Send notification when the sensor-value is less than the
                configured threshold";
            }
          }
        }
      }
    }

    notification sensor-threshold-crossed {
      description "Notifications to be sent when a sensor value crosses
                  a configured threshold.
                  PD - An additional sensor name is not needed in this case since it is augmented under component
                  and the 'name' leaf will be provided with the notification";

      leaf name {
        type leafref {
          path "/hw:hardware/hw:component[hw:name=current()/../../hw:name]"
               + "/sensor-notifications/threshold/name";
        }
        description
          "Name of the sensor-threshold.";
      }

      choice threshold-value {
        case max {
          leaf max {
            type leafref {
              path "/hw:hardware/hw:component[hw:name=current()/../../hw:name]"
                   + "/sensor-notifications/threshold/max";
            }
          }
        }
        case min {
          leaf min {
            type leafref {
              path "/hw:hardware/hw:component[hw:name=current()/../../hw:name]"
                   + "/sensor-notifications/threshold/min";
            }
          }
        }
      }

      leaf sensor-value {
        type hw:sensor-value;
        description "PD - Functionally having this as a leafref is wrong because sensor values can differ
                    between two sensor data gets and the sensor value from the operational data request can and most of the time
                    will be different than the sensor value which triggered the notification in the first place.";
      }
    }
  }
}
